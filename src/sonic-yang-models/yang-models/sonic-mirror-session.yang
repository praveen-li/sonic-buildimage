module sonic-mirror-session {

    yang-version 1.1;

    namespace "http://github.com/Azure/sonic-mirror-session";
    prefix sms;

    import ietf-inet-types {
        prefix inet;
    }

    import sonic-port {
        prefix port;
    }

    import sonic-portchannel {
        prefix lag;
    }

    description
        "SONiC Mirror session yang model";

    revision 2021-06-15 {
        description
            "Initial revision.";
    }

    typedef session_type {
        type enumeration {
            enum ERSPAN {
                description "ERSPAN session";
            }
            enum SPAN {
                description "SPAN session";
            }
        }
    }

    typedef session_direction {
        type enumeration {
            enum RX {
                description "RX direction";
            }
            enum TX {
                description "TX direction";
            }
            enum BOTH {
                description "Both RX and TX direction";
            }
        }
    }

    container sonic-mirror-session {

        container MIRROR_SESSION {

            list MIRROR_SESSION_LIST {
                key "name";

                leaf name {
                    type string {
                        pattern '[a-zA-Z0-9]{1}([-a-zA-Z0-9_]{0,31})';
                        length 1..32 {
                            error-message "Invalid mirror session name";
                            error-app-tag session-name-invalid;
                        }
                    }
                    description
                        "Mirror session name.";
                }

                leaf type {
                    type session_type;
                    default "ERSPAN";
                    description
                        "Mirror session type.";
                }

                leaf src_ip {
                    when "current()/../type = 'ERSPAN'";
                    type inet:ipv4-address;
                    description
                        "ERSPAN source ip. This IP will be set as source ip in
                        outer header of mirrored frame ";
                }

                leaf dst_ip {
                    when "current()/../type = 'ERSPAN'";
                    type inet:ipv4-address;
                    description
                        "ERSPAN destination ip. Mirrored frames will be routed to this destination.
                        This IP will be set as destination ip in outer header of mirrored frame ";
                }

                leaf gre_type {
                    when "current()/../type = 'ERSPAN'";
                    type string {
                        pattern "0[xX][0-9a-fA-F]*|([0-9]|[1-5]?[0-9]{2,4}|6[1-4][0-9]{3}|65[1-4][0-9]{2}|655[1-2][0-9]|6553[0-5])";
                        length 1..6 {
                            error-message "Invalid GRE type";
                            error-app-tag gre-type-invalid;
                        }
                    }
                    default 0x88be;
                    description
                        "ERSPAN outer header GRE type.";
                }

                leaf dscp {
                    when "current()/../type = 'ERSPAN'";
                    type uint8 {
                        range "0..63" {
                            error-message "Invalid dscp value";
                            error-app-tag dscp-invalid;
                        }
                    }
                    description
                        "ERSPAN outer header DSCP value. Mirrored frames will be sent with configured DSCP value";
                }

                leaf ttl {
                    when "current()/../type = 'ERSPAN'";
                    type uint8 {
                        range "0..63" {
                            error-message "Invalid TTL value";
                            error-app-tag ttl-invalid;
                        }
                    }
                    description
                        "ERSPAN outer header TTL value. Mirrored frames will be sent with configured TTL value";
                }

                leaf queue {
                    type uint8;
                    description
                        "ERSPAN Queue. Mirrored frames will be sent to this queue";
                }

                leaf dst_port {
                    when "current()/../type = 'SPAN'";
                    type union {
                        type leafref {
                            path "/port:sonic-port/port:PORT/port:PORT_LIST/port:port_name";
                        }
                        type string {
                            pattern "CPU";
                        }
                    }
                    description
                        "Destination port configuration for port mirroring(SPAN).";
                }

                leaf-list src_port {
                    type union {
                        type leafref {
                            path "/port:sonic-port/port:PORT/port:PORT_LIST/port:port_name";
                        }
                        type leafref {
                            path "/lag:sonic-portchannel/lag:PORTCHANNEL/lag:PORTCHANNEL_LIST/lag:portchannel_name";
                        }
                    }
                    description
                        "Source port configuration for mirroring. Can be configured for both SPAN/ERSPAN.
                        Supports both port and port-channel as arguments";
                }

                leaf direction {
                    type session_direction;
                    default "BOTH";
                    description
                        "Direction configuration for mirroring. Can be configured for both SPAN/ERSPAN.
                        Supports rx/tx/both as direction config.
                           RX: Captures frames ingressing on source port.
                           TX: Captures frames egressing on source port.
                           BOTH: Captures frames ingressing or egressing on source port.";
                }
            }
        }
    }
}
