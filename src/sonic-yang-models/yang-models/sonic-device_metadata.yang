module sonic-device_metadata {

    yang-version 1.1;

    namespace "http://github.com/Azure/sonic-device_metadata";
    prefix device_metadata;

    import ietf-yang-types {
        prefix yang;
    }

    import ietf-inet-types {
        prefix inet;
    }

    import sonic-types {
        prefix stypes;
        revision-date 2019-07-01;
    }

    description "DEVICE_METADATA YANG Module for SONiC OS";

    revision 2020-04-10 {
        description "First Revision";
    }

    container sonic-device_metadata {

        container DEVICE_METADATA {

            description "DEVICE_METADATA part of config_db.json";

            container localhost{

                leaf hwsku {
                    type stypes:hwsku;
                }

                leaf default_bgp_status {
                    type enumeration {
                        enum up;
                        enum down;
                    }
                    default up;
                }

                leaf docker_routing_config_mode {
                    type string {
                        pattern "unified|split|separated";
                    }
                    default "unified";
                }

                leaf hostname {
                    type string {
                        length 1..255;
                    }
                }

                leaf platform {
                    type string {
                        length 1..255;
                    }
                }

                leaf mac {
                    type yang:mac-address;
                }

                leaf default_pfcwd_status {
                    type enumeration {
                        enum disable;
                        enum enable;
                    }
                    default disable;
                }

                leaf bgp_asn {
                    type inet:as-number;
                }

                leaf deployment_id {
                    type uint32;
                }

                leaf type {
                    type string {
                        length 1..255;
                        pattern "ToRRouter|LeafRouter|SpineRouter|SpineChassisFrontendRouter|ChassisBackendRouter|ASIC";
                    }
                }

                leaf buffer_model {
                    type string;
                }

                leaf cloudtype {
                    type string;
                }

                leaf region {
                    type string;
                }

                leaf synchronous_mode {
                    type string;
                }
            }
            /* end of container localhost */

            /* container for TLS Cert */
            container x509 {
                leaf ca_crt {
                    type string;
                }
                leaf server_crt {
                    type string;
                }
                leaf server_key {
                    type string;
                }
            }
            /* end of container for TLS Cert */
        }
        /* end of container DEVICE_METADATA */
    }
    /* end of top level container */
}
/* end of module sonic-device_metadata */
