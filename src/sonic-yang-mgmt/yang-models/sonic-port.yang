module sonic-port{

	namespace "http://github.com/Azure/sonic-port";
	prefix port;

	import ietf-yang-types {
		prefix yang;
	}

	import ietf-inet-types {
		prefix inet;
	}

	import sonic-head {
		prefix head;
		revision-date 2019-07-01;
	}

	organization "Linkedin Corporation";

	contact "lnos_coders@linkedin.com";

	description "PORT yang Module for SONiC OS";

	revision 2019-07-01 {
		description "First Revision";
	}

	container sonic-port{
		container PORT {

			description "PORT part of config_db.json";

			list PORT_LIST {

				key "port_name";

				leaf port_name {
					type string {
						length 1..128;
					}
				}

				leaf alias {
					type string {
						length 1..128;
					}
				}

				leaf lanes {
					type string {
						length 1..128;
					}
				}

				leaf description {
					type string {
						length 0..255;
					}
				}

				leaf speed {
					type uint32 {
						range 1..100000;
					}
				}

				leaf mtu {
					type uint16 {
						range 1..9216;
					}
				}

				leaf admin_status {
					mandatory true;
					type head:admin_status;
				}

				leaf fec {
					type string {
						pattern "rc|fc|None";
					}
				}
			} /* end of list PORT_LIST */

		} /* end of container PORT */

	} /* end of container sonic-port */

} /* end of module sonic-port */
